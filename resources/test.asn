Lightweight-Directory-Access-Protocol-V3

DEFINITIONS IMPLICIT TAGS ::=

BEGIN

LDAPMessage ::= SEQUENCE {
  messageID   MessageID,
  protocolOp  CHOICE {
                bindRequest      BindRequest,
                bindResponse     BindResponse,
                unbindRequest    UnbindRequest,
                searchRequest    SearchRequest,
                searchResEntry   SearchResultEntry,
                searchResDone    SearchResultDone,
                searchResRef     SearchResultReference,
                modifyRequest    ModifyRequest,
                modifyResponse   ModifyResponse,
                addRequest       AddRequest,
                addResponse      AddResponse,
                delRequest       DelRequest,
                delResponse      DelResponse,
                modDNRequest     ModifyDNRequest,
                modDNResponse    ModifyDNResponse,
                compareRequest   CompareRequest,
                compareResponse  CompareResponse,
                abandonRequest   AbandonRequest,
                extendedReq      ExtendedRequest,
                extendedResp     ExtendedResponse },
  controls    [0] Controls OPTIONAL
}
  
MessageID ::= INTEGER (0 .. maxInt)
  
maxInt INTEGER ::= 2147483647 -- (2^^31 - 1) --

LDAPString ::= OCTET STRING

LDAPOID ::= OCTET STRING

LDAPDN ::= LDAPString

RelativeLDAPDN ::= LDAPString

AttributeType ::= LDAPString

AttributeDescription ::= LDAPString

AttributeDescriptionList ::= SEQUENCE OF AttributeDescription

AttributeValue ::= OCTET STRING

AttributeValueAssertion ::= SEQUENCE {
   attributeDesc   AttributeDescription,
   assertionValue  AssertionValue
}

AssertionValue ::= OCTET STRING

Attribute ::= SEQUENCE {
   type  AttributeDescription,
   vals  SET OF AttributeValue
}

MatchingRuleId ::= LDAPString

LDAPResult ::= SEQUENCE {
  resultCode    ENUMERATED {
                  success                      (0),
                  operationsError              (1),
                  protocolError                (2),
                  timeLimitExceeded            (3),
                  sizeLimitExceeded            (4),
                  compareFalse                 (5),
                  compareTrue                  (6),
                  authMethodNotSupported       (7),
                  strongAuthRequired           (8),
                    -- 9 reserved --
                  referral                     (10), -- new
                  adminLimitExceeded           (11), -- new
                  unavailableCriticalExtension (12), -- new
                  confidentialityRequired      (13), -- new
                  saslBindInProgress           (14), -- new
                  noSuchAttribute              (16),
                  undefinedAttributeType       (17),
                  inappropriateMatching        (18),
                  constraintViolation          (19),
                  attributeOrValueExists       (20),
                  invalidAttributeSyntax       (21),
                    -- 22-31 unused --
                  noSuchObject                 (32),
                  aliasProblem                 (33),
                  invalidDNSyntax              (34),
                    -- 35 reserved for undefined isLeaf --
                  aliasDereferencingProblem    (36),
                    -- 37-47 unused --
                  inappropriateAuthentication  (48),
                  invalidCredentials           (49),
                  insufficientAccessRights     (50),
                  busy                         (51),
                  unavailable                  (52),
                  unwillingToPerform           (53),
                  loopDetect                   (54),
                    -- 55-63 unused --
                  namingViolation              (64),
                  objectClassViolation         (65),
                  notAllowedOnNonLeaf          (66),
                  notAllowedOnRDN              (67),
                  entryAlreadyExists           (68),
                  objectClassModsProhibited    (69),
                    -- 70 reserved for CLDAP --
                  affectsMultipleDSAs          (71), -- new
                    -- 72-79 unused --
                  other                        (80) },
                    -- 81-90 reserved for APIs --
  matchedDN     LDAPDN,
  errorMessage  LDAPString,
  -- referral      [3] Referral OPTIONAL
}

Referral ::= SEQUENCE OF LDAPURL

LDAPURL ::= LDAPString -- limited to characters permitted in URLs

Controls ::= SEQUENCE OF Control

Control ::= SEQUENCE {
  controlType   LDAPOID,
  criticality   BOOLEAN DEFAULT FALSE,
  controlValue  OCTET STRING OPTIONAL }

BindRequest ::= [APPLICATION 0] SEQUENCE {
  version         INTEGER (1 .. 127),
  name            LDAPDN,
  authentication  AuthenticationChoice }

AuthenticationChoice ::= CHOICE {
   simple  [0] OCTET STRING,
            -- 1 and 2 reserved
   sasl    [3] SaslCredentials }

SaslCredentials ::= SEQUENCE {
  mechanism    LDAPString,
  credentials  OCTET STRING OPTIONAL }

BindResponse ::= [APPLICATION 1] SEQUENCE {
  resultCode    ENUMERATED {
                  success                      (0),
                  operationsError              (1),
                  protocolError                (2),
                  timeLimitExceeded            (3),
                  sizeLimitExceeded            (4),
                  compareFalse                 (5),
                  compareTrue                  (6),
                  authMethodNotSupported       (7),
                  strongAuthRequired           (8),
                    -- 9 reserved --
                  referral                     (10), -- new
                  adminLimitExceeded           (11), -- new
                  unavailableCriticalExtension (12), -- new
                  confidentialityRequired      (13), -- new
                  saslBindInProgress           (14), -- new
                  noSuchAttribute              (16),
                  undefinedAttributeType       (17),
                  inappropriateMatching        (18),
                  constraintViolation          (19),
                  attributeOrValueExists       (20),
                  invalidAttributeSyntax       (21),
                    -- 22-31 unused --
                  noSuchObject                 (32),
                  aliasProblem                 (33),
                  invalidDNSyntax              (34),
                    -- 35 reserved for undefined isLeaf --
                  aliasDereferencingProblem    (36),
                    -- 37-47 unused --
                  inappropriateAuthentication  (48),
                  invalidCredentials           (49),
                  insufficientAccessRights     (50),
                  busy                         (51),
                  unavailable                  (52),
                  unwillingToPerform           (53),
                  loopDetect                   (54),
                    -- 55-63 unused --
                  namingViolation              (64),
                  objectClassViolation         (65),
                  notAllowedOnNonLeaf          (66),
                  notAllowedOnRDN              (67),
                  entryAlreadyExists           (68),
                  objectClassModsProhibited    (69),
                    -- 70 reserved for CLDAP --
                  affectsMultipleDSAs          (71), -- new
                    -- 72-79 unused --
                  other                        (80) },
                    -- 81-90 reserved for APIs --
  matchedDN     LDAPDN,
  errorMessage  LDAPString,
  referral      [3] Referral OPTIONAL,
  -- COMPONENTS OF LDAPResult,
  serverSaslCreds  [7] OCTET STRING OPTIONAL }
  
END
